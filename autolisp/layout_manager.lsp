(defun c:LAYOUTMGR (/ *error* layout-list layout-name new-name new-order action doc layouts) 
  (vl-load-com)
  (defun *error* (msg)
    (if msg
      (princ (strcat "\nError: " msg))
    )
    (princ)
  )
  (setq doc (vla-get-activedocument (vlax-get-acad-object)))
  (setq layouts (vla-get-layouts doc))
  (setq layout-list '())
  (vlax-for layout layouts
    (setq layout-list (cons (vla-get-name layout) layout-list))
  )
  (setq layout-list (reverse layout-list))
  (initget "Rename Reorder Create Delete")
  (setq action (getkword "\nChoose action [Rename/Reorder/Create/Delete]: "))
  (cond
    ((= action "Rename")
      (setq layout-name (getstring "\nEnter current layout name to rename: "))
      (setq new-name (getstring "\nEnter new layout name: "))
      (if (and (member layout-name layout-list)
               (not (member new-name layout-list)))
        (progn
          (setq layout (vla-item layouts layout-name))
          (vla-put-name layout new-name)
          (princ (strcat "\nLayout renamed from " layout-name " to " new-name))
        )
        (princ "\nInvalid layout name or new name already exists.")
      )
    )
    ((= action "Reorder")
      (princ "\nCurrent layout order:")
      (foreach l layout-list (princ (strcat "\n" l)))
      (setq layout-name (getstring "\nEnter layout name to move: "))
      (if (member layout-name layout-list)
        (progn
          (setq new-order (getint (strcat "\nEnter new position (1-" (itoa (length layout-list)) "): ")))
          (if (and (>= new-order 1) (<= new-order (length layout-list)))
            (progn
              (setq layout-list (vl-remove layout-name layout-list))
              (setq layout-list (append (sublist layout-list 0 (1- new-order))
                                        (list layout-name)
                                        (sublist layout-list (1- new-order) nil)))
              (setq index 0)
              (foreach l layout-list
                (setq layout (vla-item layouts l))
                (vla-put-taborder layout (1+ index))
                (setq index (1+ index))
              )
              (princ "\nLayout order updated.")
            )
            (princ "\nInvalid position.")
          )
        )
        (princ "\nLayout not found.")
      )
    )
    ((= action "Create")
      (setq new-name (getstring "\nEnter new layout name: "))
      (if (not (member new-name layout-list))
        (progn
          (vla-add layouts new-name)
          (princ (strcat "\nLayout " new-name " created."))
        )
        (princ "\nLayout name already exists.")
      )
    )
    ((= action "Delete")
      (setq layout-name (getstring "\nEnter layout name to delete: "))
      (if (and (member layout-name layout-list)
               (not (wcmatch (strcase layout-name) "MODEL")))
        (progn
          (setq layout (vla-item layouts layout-name))
          (vla-delete layout)
          (princ (strcat "\nLayout " layout-name " deleted."))
        )
        (princ "\nCannot delete Model layout or layout not found.")
      )
    )
  )
  (princ)
)

;; Helper function to get sublist
(defun sublist (lst start end / result)
  (setq result '())
  (if (null end)
    (setq end (length lst))
  )
  (while (and (< start end) (< start (length lst)))
    (setq result (cons (nth start lst) result))
    (setq start (1+ start))
  )
  (reverse result)
)

(princ "\nLAYOUTMGR loaded. Type LAYOUTMGR to run.")
(princ)
